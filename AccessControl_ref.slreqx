# AccessControl_ref

## #1: Должно быть обеспечено чтение RFID-метки (Functional)

## #2: Данные извлеченные из RFID-метки должны быть переданы во внешнюю базу данных ODBC (Functional)

## #3: На основе ответа базы данных вырабатывается запрет или разрешение доступа (Functional)

## #4: Пользователь должен быть извещен о статусе доступа (Functional)

## #5: Замок разблокируется на основе статусе доступа (Functional)
